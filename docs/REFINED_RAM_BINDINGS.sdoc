[DOCUMENT]
TITLE: Gap closure and refined RAM bindings

[REQUIREMENT]
UID: CIL-GAPS-001
TITLE: Close retained opcode and diagnostic test gaps
STATEMENT: >>>
Exercise reference pop, signed element loads and native conv.i4 length
normalization against CLR and Core behavior. Require actionable reasons for
height, stack-shape, native-branch and mixed-comparison diagnostics. Replay the
seven retained mutations without treating earlier equivalent survivors as defects.
Verification: ScheduledAliasGapTests and focused Stryker evidence.
<<<

[REQUIREMENT]
UID: CIL-NULL-001
TITLE: Branch-sensitive null refinement with invalidation
STATEMENT: >>>
Refine tested reference locals separately on taken and fallthrough edges for
reference truth, null equality/inequality and supported null predicates stored
in Boolean locals. Invalidate dependent predicates and older stack provenance
on writes to the tested local. Preserve fixed-point joins over loops and reject
stale or unguarded nullable dereferences. Identical target/fallthrough edges must
not lose reachability. Impossible runtime control targets terminate with fault.
Verification: ScheduledNullRefinementTests and guarded CLR/HDL replay.
<<<

[REQUIREMENT]
UID: CIL-RAMS-001
TITLE: Bounded distinct physical RAM origins
STATEMENT: >>>
Support up to eight immutable uint[] parameter bindings as distinct physical
RAMs. Carry sets of possible origins through aliases and joins; dispatch loads,
stores and lengths using the actual origin tag. Null and invalid tags must not
access memory. Apply depth and initial contents per original parameter index;
reject invalid configuration and ambiguous legacy initialization. Preserve
capture, reset, bounds faults and earlier committed writes. Distinct physical
bindings do not model runtime aliasing between caller-supplied parameter objects.
Verification: ScheduledMultipleRamTests, guarded RAM CLR/HDL replay and fuzzing.
<<<
