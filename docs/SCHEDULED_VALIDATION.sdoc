[DOCUMENT]
TITLE: Scheduled machine compiler boundary requirements

[REQUIREMENT]
UID: CIL-DIAG-001
TITLE: Structured source-aware CIL rejection
STATEMENT: >>>
Compiler rejections shall retain NotSupportedException compatibility while exposing
the original method, IL offset, actionable reason and a matched visible source span
where available. Hidden/missing source shall remain explicitly absent. Malformed
or unreadable optional symbols shall not replace the primary rejection; their
failure shall be retained and identified in the diagnostic and exception.
Implementation: CilDiagnostic.cs and CilCompiler.Error.
Verification: CilDiagnosticTests covers visible, hidden, dynamic-image, malformed
symbol, zero/negative-offset, global-method and unrelated-exception cases.
<<<

[REQUIREMENT]
UID: SCHED-VAL-001
TITLE: Expression ownership
STATEMENT: >>>
The scheduled builder shall reject any expression containing an input or register
leaf owned by another builder at every public expression sink. Constants may be
shared. Validation shall inspect nested operands and shared DAGs.
Implementation: src/SharpHDL.HLS/ScheduledMachine.cs, ValidateValue.
Verification: ScheduledMachineValidationTests.Foreign_expression_leaves_are_rejected,
Nested_foreign_expression_fuzz, Local_shared_dag_matches_exhaustive_byte_reference.
<<<

[REQUIREMENT]
UID: SCHED-VAL-002
TITLE: Successful lowering freezes state handles
STATEMENT: >>>
Successful lowering shall prohibit further assignments, transitions, memory
accesses and resource reservations through retained state handles. Failed
validation shall leave the model editable to repair an unknown transition.
Implementation: ScheduledMachine.cs, Lower, ValidateOwned and ValidateValue.
Verification: Lowering_freezes_every_state_mutation and
Unknown_transition_can_be_repaired_after_failed_lowering.
<<<

[REQUIREMENT]
UID: SCHED-VAL-003
TITLE: Transactional declarations and reserved names
STATEMENT: >>>
A rejected declaration shall not consume its name. The compiler-generated
scheduler_state name shall be reserved against all user hardware declarations.
Implementation: ScheduledMachine.cs, declaration methods and names registry.
Verification: Invalid_declarations_are_transactional,
Invalid_width_fuzz_preserves_builder and Scheduler_state_name_is_reserved.
<<<

[REQUIREMENT]
UID: SCHED-TABLE-001
TITLE: Non-FIR synchronous table example
STATEMENT: >>>
An explicit scheduled table shall accept a key, unsigned 16-bit delta and update
flag; return the original or modulo-65536 updated value after three edges; hold
response data while stalled; and admit a new request only after the prior response.
A synchronous reset shall abort pending responses, suppress the reset-edge write
and retain committed RAM contents. Support power-of-two depths from 2 to 256.
Implementation: examples/ScheduledTable.cs.
Verification: ScheduledTableTests.Table_matches_independent_array_and_protocol_model;
ScheduledTableCampaign; ScheduledTableReplay generated RTL, Icarus and Yosys.
This is an explicit schedule, not automatic scheduling of arbitrary CIL.
<<<

[REQUIREMENT]
UID: BUILD-REG-001
TITLE: Regression project isolation
STATEMENT: >>>
The standalone tests/Tests.csproj executable shall compile its root regression
sources without including nested test projects or generated intermediates. It
shall retain the internal API access required by existing structural checks.
Implementation: tests/Tests.csproj and src/SharpHDL/SharpHDL.csproj.
Verification: dotnet run --project tests/Tests.csproj -c Release.
<<<

[REQUIREMENT]
UID: TEST-PROV-001
TITLE: Isolated output portability
STATEMENT: >>>
The source-provenance regression shall locate checkout sources independently of
its build-output directory, including native Linux artifacts outside the checkout.
Implementation and verification: HardwareSourceProvenanceTests,
Generated_pipeline_emits_only_real_source_and_RTL_locations.
<<<

[REQUIREMENT]
UID: SCHED-ARITH-001
TITLE: Typed shared arithmetic binding
STATEMENT: >>>
The scheduler shall declare width/operation-compatible Add, Subtract or Multiply
resources with positive physical capacity. Per-state bindings shall lower to
reusable operand arbitration and state/guard-gated result routing, with at most
one operation per instance per state. Oversubscription is rejected regardless of
guard values. Chained bound operations require explicit register boundaries.
Implementation: ScheduledArithmetic.cs; HlsScheduledFirCompiler now consumes it.
Verification: ScheduledArithmeticTests and existing FIR simulation/RTL replays.
Execution evidence: FOLLOWUP_2026-10-27.md and verification/followup-2026-10-27.json.
<<<

[REQUIREMENT]
UID: SCHED-VERIFY-002
TITLE: Semantic mutation and coverage-guided fuzzing
STATEMENT: >>>
Verification shall challenge assignment/transition priority, simultaneous register
commit, hold/reset, numeric/declaration boundaries and ownership. A bounded
SharpFuzz/AFL++ campaign shall compare table execution with an independent array
oracle; retain seed, coverage/queue/crash evidence and reproducible commands.
Stryker shall mutate both scheduled compiler sources and the table implementation.
Equivalent mutations shall be distinguished from untested behavior.
Implementation: ScheduledSemanticTests, ScheduledFuzz and run-scheduled-fuzz.sh.
Execution and mutant disposition: FOLLOWUP_2026-10-27.md and verification/followup-mutant-dispositions.json.
<<<

[REQUIREMENT]
UID: CIL-SCHED-001
TITLE: Stateful CIL through scheduled Core lowering
STATEMENT: >>>
An opt-in frontend shall reuse existing CIL decoding and stack/control-flow
analysis to lower static integer/Boolean control flow, runtime loops and one
uint[] RAM through ScheduledMachineBuilder. Instructions execute one per edge;
loads add one wait edge; arguments latch only on start while idle. Bounds/watchdog
faults complete explicitly. Register reset retains committed RAM writes. Preserve
method/IL-offset state provenance and reject unsupported opcodes without fallback.
Implementation: ScheduledSequentialCil.cs; ScheduledValue integer operations.
Verification: ScheduledCilTests compares host results and legacy outputs edge by
edge, including repeat calls, bounds/watchdog and unsupported-opcode diagnostics.
Execution evidence: FOLLOWUP_2026-10-27.md; this does not replace the broader legacy API.
<<<

[REQUIREMENT]
UID: SCHED-PARITY-001
TITLE: Reset phase and independent HDL parity
STATEMENT: >>>
Directed tests shall reset at every table control phase and distinguish suppressed
writes from already committed updates. Independently scheduled machines shall not
share runtime state. Compact vector replays shall check table and stateful CIL
outputs after every edge in Icarus and Verilator, after independent host/legacy
checks during generation. Local Windows/Linux xUnit and RTL runs gate changes; GitHub Actions remains disabled per the user instruction of 2026-10-27.
Implementation: ScheduledResetTests, CoreReplay, ScheduledSuiteReplay and xunit.yml.
Execution results and confirmation of disabled Actions are recorded at final push.
This does not implement shared-resource arbitration among concurrent kernels.
<<<

[REQUIREMENT]
UID: SCHED-MEM-001
TITLE: Explicit bank ports and inference policy
STATEMENT: >>>
Scheduled hardware shall declare independent cyclic single-port banks, exact
immutable initialization and validated vendor inference hints. Distinct banks may
be accessed concurrently; same-bank conflicts remain rejected. Reset retains
committed words. Mapping shall preserve bank/row identity and diagnose bounds.
RTL shall preserve requested hints without claiming physical implementation.
Verification includes independent array checks, generic and Xilinx synthesis
resource evidence and a reproducible BenchmarkDotNet baseline before optimizing.
Implementation: ScheduledMemoryBanks, HardwareMemoryPort, CoreVerilogEmitter and
ScheduledBankedTable. Tests: ScheduledBankedMemoryTests; final campaign evidence.
<<<

[REQUIREMENT]
UID: CIL-SCHED-SHIFT-001
TITLE: Exact Int32 shift semantics
STATEMENT: >>>
The scheduled CIL frontend shall lower shl, shr and shr.un using only the five low
count bits for 32-bit operands, including negative and oversized count patterns.
Signed right shift replicates the sign; unsigned right shift inserts zeros; left
shift wraps at 32 bits. Static scheduled shifts preserve exact-width semantics
and reject negative offsets. Oversized static offsets must not cause unbounded
host allocations. Existing instruction-per-edge timing and watchdog/reset apply.
Implementation: ScheduledCilShiftLowering.cs and ScheduledValue shift operations.
Verification: ScheduledShiftTests native/legacy comparisons, generated properties,
exhaustive byte references and ScheduledCilShifts Icarus/Verilator replay.
Execution is recorded in the end-of-slice verification report.
<<<

[REQUIREMENT]
UID: CIL-SCHED-SOURCE-001
TITLE: Matched source provenance for encoded control states
STATEMENT: >>>
Scheduled CIL compilation shall expose actual scheduler-state encodings, original
IL offsets and matched Portable PDB source spans. Idle/hidden/unmapped states
have null source locations. Sidecar and embedded symbols shall be matched to the
PE identity; mismatched/missing symbols may not fabricate locations. Malformed
symbol data and unexpected IO errors remain visible. Document checksum metadata
is reported without implying that the local document was verified automatically.
Existing pipeline annotation shall not extend visible spans across hidden points.
Implementation: PortablePdbMethodMap, PortablePdbSourceMap, ScheduledCilCompilation.
Verification: ScheduledSourceMapTests including embedded fixture, real checksums,
hidden regions, missing/mismatched/malformed providers, and source-map JSON export.
<<<
