[DOCUMENT]
TITLE: Tool execution, equivalence, latency scheduling, performance and documentation

[REQUIREMENT]
UID: TOOL-RUN-001
TITLE: Literal subprocess arguments and retained evidence
STATEMENT: >>>
The HDL runner shall execute absolute programs without a shell, preserve separate
arguments, drain stdout/stderr concurrently with finite per-stream byte limits,
close stdin and retain raw logs and JSON provenance in a new artifact directory.
Nonzero exit, absent/unstartable executable and truncated output shall not succeed.
Implementation: SharpHDL.Tooling.HdlToolRunner and SharpHDL.ToolCli.
Verification: HdlToolRunnerTests, generated argv properties and run-scheduled-rtl.sh.
<<<

[REQUIREMENT]
UID: TOOL-RUN-002
TITLE: Cancellable ordinary process trees
STATEMENT: >>>
The runner shall distinguish caller cancellation from deadline expiry, terminate
the ordinary process tree and observe pipe tasks before returning. Cleanup/IO
errors shall propagate. Detached/reparented daemon containment is unsupported;
the runner is not a sandbox. Evidence directories shall never be overwritten.
Verification: Cancellation_terminates_an_ordinary_process_tree and timeout/limit tests.
<<<

[REQUIREMENT]
UID: BV-EQUIV-001
TITLE: Bounded combinational equivalence with no silent omissions
STATEMENT: >>>
The verifier shall compare two outputs over all matching ordinal input valuations
using real Z3 4.12.2 bit vectors. Support only 1..256-node combinational graphs,
1..32-bit values and at most 128 total input bits with unique bounded ASCII input
identifiers. Reject every state boundary, RAM, ROM and DSP primitive, including
unused unsupported nodes. Explicit signed operations, modular arithmetic, shifts,
slices, zero/sign extension and concatenation shall preserve Core semantics.
Implementation: SharpHDL.Verification.BitVectorEquivalence.
Verification: complete small truth tables, CLR arithmetic properties and independent
Yosys checks in SharpHDL.EquivalenceCli. This is not sequential equivalence.
<<<

[REQUIREMENT]
UID: BV-EQUIV-002
TITLE: Retained counterexamples and nonproof outcomes
STATEMENT: >>>
Only a completed UNSAT result shall denote Equivalent. SAT valuations shall
reproduce differing outputs in the independent Core evaluator before Different
is returned. Retain SMT-LIB, native version and concrete decimal input values.
Resource exhaustion/timeout, cancellation, unsupported inputs and unavailable or
mismatched native assets shall never be classified as equivalent. Retain actual
Yosys counterexamples in the independent qualification campaign.
Counterexample evaluation shall bound constant shifts by the hardware result
width before host arithmetic, avoiding unbounded intermediate BigInteger allocation.
Verification: Native_resource_exhaustion_and_precancellation_do_not_prove_equivalence,
profile rejection tests, deliberately corrupted truth tables and retained native runs.
<<<

[REQUIREMENT]
UID: REGION-SCHED-001
TITLE: Source-order typed-effect hazards and deterministic intervals
STATEMENT: >>>
Automatic straight-line regions shall infer register RAW/WAR/WAW hazards and
potential memory aliases from actual typed operation bodies in semantic source
order. Shared memory objects alias; distinct literal addresses can be disjoint;
unknown addresses may alias. Ready independent work shall use ordinal-name
priority and reserve every required physical resource throughout its latency.
Reject missing/foreign/duplicate/unscheduled bodies, malformed intervals and
overbooking. Validate proposed assignments independently and retain canonical maps.
Implementation: ScheduledRegions.cs. Verification: ScheduledRegionTests including
generated register programs, address aliases, mixed latencies and exact budgets.
The bounded profile supports 128 operations, 4095 edges and no control-flow loops.
<<<

[REQUIREMENT]
UID: REGION-SCHED-002
TITLE: Actual registered iterative arithmetic and lowerer checks
STATEMENT: >>>
A 2..32-bit shift-add multiplier shall sample operands once, consume one operand
bit per active edge and commit the modular result after Width edges. Shared
instances shall have initiation interval Width and reserve all phases. Lower
shall independently check emitted reservation gates and real memory ports.
No multiply primitive or latency-only placeholder shall replace the iterative unit.
Verification: width/capture/reset tests, independent modular properties, twelve-design
Icarus/Verilator replay and generic Yosys checks. Physical timing is unqualified.
<<<

[REQUIREMENT]
UID: DOC-BUILD-001
TITLE: Reproducible engineering and compiler XML documentation
STATEMENT: >>>
Build curated existing engineering Markdown with Sphinx/MyST and compiler-emitted
XML documentation for seven managed framework assemblies. Fail on Sphinx warnings
and nonzero tool results; retain tool manifests. Keep documentation-only Python
dependencies opt-in, separate from ordinary managed builds. Explicitly disclose
legacy missing XML comments and browser-CDN Mermaid rendering limitations.
Verification: DocumentationCatalogTests, actual site build and retained summary.
<<<

[REQUIREMENT]
UID: DOC-TRACE-001
TITLE: Preserve bounded and incomplete requirement evidence
STATEMENT: >>>
Read requirements from the real StrictDoc JSON exporter. Validate manually
reviewed trace rows against known stable UIDs and existing repository-contained
source, test and evidence files. Reject unknown statuses, missing references and
path escapes. Preserve partial, historical and unmapped requirements; do not
promote requirement status by building documentation. Test-name text admission
is not semantic symbol resolution, test execution or automatic requirement closure.
Verification: DocumentationCatalogTests and generated authoritative trace ledger.
<<<

[REQUIREMENT]
UID: BUILD-DEPS-001
TITLE: Draft inferred container-fixture dependency audit
STATEMENT: >>>
Inferred from the required warning-sensitive build review: do not suppress known
high-severity dependency advisories in the optional container test project.
Constrain its transitive SSH.NET dependency to patched 2026.0.0 and retain a
successful restore/build and transitive vulnerability-audit result. Preserve the
existing Testcontainers builder API in this slice. Local/remote Docker and SCP
behavior require separate runtime qualification; compilation is not conformance.
Verification: integration project warning-as-error build and NuGet audit evidence.
<<<
