[DOCUMENT]
TITLE: Scheduled typed stack and bound RAM aliases

[REQUIREMENT]
UID: CIL-TYPE-001
TITLE: Validate intermediate stack categories before lowering
STATEMENT: >>>
Validate reachable evaluation-stack categories and every declared argument/local
index before allocating hardware. Reject integer/reference confusion in numeric,
return, conversion, storage and memory operands, including same-height incompatible
control-flow merges. Preserve bounded native array-length category until explicit
conv.i4/u4 normalization. Include original method and IL-offset diagnostics.
Do not claim general CLI verification or native-integer arithmetic support.
Verification: ScheduledTypedStackTests and existing scheduled compiler regression.
<<<

[REQUIREMENT]
UID: CIL-ALIAS-001
TITLE: Flow-sensitive aliases of one immutable bound RAM
STATEMENT: >>>
Permit initialized uint[] local aliases of the single bound RAM. Track null,
bound and their union across stack/local copies, joins and backedges to a fixed
point. Reject dereferences unless provenance is definitely bound; reject numeric
fabrication and rebinding the RAM argument. Permit reference truth/equality and
cgt.un against definite null using null/bound identity tags. Allocate one physical
RAM and one-bit reference local tags, clear tags at reset/accepted start, and
preserve normal capture, bounds faults and earlier RAM writes. Bound combined
arguments/locals at 1024. Do not claim path refinement, multiple array origins,
general pointer semantics or whole sequential equivalence.
Verification: ScheduledArrayAliasTests, native CLR/HDL replay and fuzz campaigns.
<<<
