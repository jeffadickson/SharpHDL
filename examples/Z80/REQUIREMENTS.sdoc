[DOCUMENT]
TITLE: Z80 architectural hardware test design

[REQUIREMENT]
UID: Z80-CORE-001
TITLE: Synthesizable instruction test core
STATEMENT: >>>
The Z80 example shall elaborate through ScheduledMachineBuilder into Core IR and
Verilog, execute the documented supported base/CB instruction subset, and expose
architectural state without executing a host software emulator as hardware.
Implementation: examples/Z80/Z80TestCore.cs, Build.
Verification: Z80Tests.Published_instruction_vectors_match_architectural_results;
tools/SharpHDL.Z80Demo and tools/run-z80-rtl.sh.
The implementation scope in README.md is normative. This requirement does not
demand physical pin timing or undocumented Q/WZ conformance.
<<<

[REQUIREMENT]
UID: Z80-BUS-001
TITLE: Deterministic stalled byte bus
STATEMENT: >>>
Only a valid/ready edge shall accept a byte transfer. Request address, direction,
data and valid shall remain stable during stalls. Reset shall abort the pending
request. Addresses and stack pointers shall wrap modulo 65536.
Implementation: Z80TestCore bus states and fixed-width registers.
Verification: Z80Campaign.Run, Z80Tests.Reset_aborts_stalled_store_and_halt_stops_fetch,
Z80Tests.Stack_and_immediate_addresses_wrap_at_16_bits.
<<<

[REQUIREMENT]
UID: Z80-VERIFY-001
TITLE: Independent architecture and compositional verification
STATEMENT: >>>
The design shall match selected pinned upstream register/RAM vectors, an independent
integer ALU oracle with reproducible randomized inputs, and a multi-instruction
machine-code program with loops, calls, memory writes and HALT. Tests shall record
excluded state/flags and shall not infer full ISA conformance from finite vectors.
Implementation: tests/Shared/Z80Campaign.cs and tools/ImportZ80Vectors.cs.
Verification: Z80Tests.Published_instruction_vectors_match_architectural_results,
Arithmetic_flags_match_integer_reference, Machine_code_program_composes_loop_call_ram_and_halt.
<<<

[REQUIREMENT]
UID: Z80-FAULT-001
TITLE: Explicit unsupported-instruction fault
STATEMENT: >>>
Unsupported instructions shall enter a sticky fault state without issuing writes
or reporting instruction completion. Reset shall recover. Encodings whose defined
Z80 behavior is an ignored prefix or ED NOP shall follow that behavior when supported.
Implementation: Z80TestCore decode, execute and trap states.
Verification: Z80Tests.Reserved_interrupt_mode_faults_and_reset_recovers,
Undefined_ed_encodings_are_two_byte_nops and Cb_sll_shifts_in_one.
<<<

[REQUIREMENT]
UID: Z80-INDEX-001
TITLE: Indexed addressing and prefix semantics
STATEMENT: >>>
DD/FD shall select IX/IY pair and byte operations. Indexed memory operands shall
add a signed displacement modulo 65536, preserve ordinary H/L for memory-transfer
exceptions, and support indexed CB memory operations with optional register copies.
EX (SP),HL/IX/IY shall exchange both bytes without changing SP. Repeated index
prefixes shall use the last selection; ignored prefixes shall preserve base behavior.
Implementation: Z80TestCore index_mode, index_displacement, Put/PutPair and exchange states.
Verification: Indexed_instruction_vectors_match_independent_results, pinned indexed-vectors.json.
<<<

[REQUIREMENT]
UID: Z80-ED-001
TITLE: ED instructions and repeat boundaries
STATEMENT: >>>
ED shall implement 16-bit ADC/SBC, pair memory transfers, NEG, IM, RETN/RETI,
I/R transfers, nibble rotates and block transfer/compare/I/O. Undefined ED
encodings shall perform the Z80 two-byte NOP behavior. Repeat instructions shall
retire individual iterations and rewind PC when continuation is required.
Implementation: Z80TestCore ED states.
Verification: Ed_and_io_vectors_match_independent_results, Ed_repeat_vectors_match_independent_results,
Undefined_ed_encodings_are_two_byte_nops; pinned ed-vectors.json and provenance.
<<<

[REQUIREMENT]
UID: Z80-IO-001
TITLE: Ordered stalled 16-bit port transactions
STATEMENT: >>>
IN/OUT and block I/O shall qualify the byte bus with bus_io, use the full Z80
port address and commit exactly once per valid/ready edge. The testbench shall
compare address, direction and data against independently published port records.
Implementation: Z80TestCore port and block I/O states, Z80Campaign.Run.
Verification: Ed_and_io_vectors_match_independent_results and stalled port replay.
<<<

[REQUIREMENT]
UID: Z80-INT-001
TITLE: Boundary-safe interrupt modes and NMI
STATEMENT: >>>
INT shall be recognized at instruction/repeat boundaries when IFF1 is enabled
and EI delay has expired. NMI edges shall remain pending during stalled transfers
and take priority over INT. IM0 shall execute the acknowledge opcode without PC
increment; IM1 shall call 0038; IM2 shall read the wrapping I/vector pointer.
Accepted service shall preserve the correct stack return PC and wake HALT.
NMI shall preserve IFF2; RETN shall restore IFF1; RETI shall identify daisy-chain
completion. Reset shall clear pending service. Invalid debug IM=3 shall fault.
Implementation: Z80TestCore interrupt states and pending-edge registers.
Verification: Z80InterruptCampaign scenarios 0..6, Interrupts_follow_architectural_boundaries,
Reserved_interrupt_mode_faults_and_reset_recovers.
<<<
